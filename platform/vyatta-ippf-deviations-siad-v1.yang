module vyatta-ippf-deviations-siad-v1 {
	namespace "urn:vyatta.com:mgmt:vyatta-ippf-deviations-siad:1";
	prefix vyatta-ippf-deviations-siad-v1;

	import vyatta-security-v1 {
		prefix security;
	}

	import vyatta-ippf-v1 {
		prefix ippf;
	}

	organization "AT&T Inc.";
	contact
		"AT&T
		 Postal: 208 S. Akard Street
		         Dallas, TX 75202, USA
		 Web: www.att.com";

	description
		"Copyright (c) 2020, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for Vyatta IP Packet Filter";

	revision 2020-10-14 {
		description "Adding egress ACL support for IP_DSCP & IPv6 HopLimit.";
	}

	revision 2020-06-25 {
		description "Fix IPv6 TCAM input constraints.";
	}

	revision 2020-05-28 {
		description
			"Preclude the additional ingress match criteria:
			  - TTL
			  - DSCP
			  - ICMP (IPv4) type/code
			  - ICMPv6 type/code
			  - ICMPv6 class
			  - L4 ports
			at Egress IP Packet Filter.
			Constrain IPv6 input rules for TCAM.
			Support counters at Egress IP Packet Filter.";
	}

	revision 2020-04-03 {
		description "Initial revision.";
	}

	deviation /security:security/ippf:ip-packet-filter/ippf:group/ippf:rule/ippf:match/ippf:fragment {
		deviate add {
			must "../../../ippf:ip-version = 'ipv4' or
				../ippf:protocol/ippf:base/ippf:number = 44 or
				../ippf:protocol/ippf:base/ippf:name = 'ipv6-frag'" {
				error-message "IPv6 group rules that match on fragments must also match on 'ipv6-frag' protocol base";
			}
		}
	}

	deviation /security:security/ippf:ip-packet-filter/ippf:group/ippf:rule/ippf:match/ippf:protocol/ippf:final {
		deviate not-supported;
	}

	deviation /security:security/ippf:ip-packet-filter/ippf:interface/ippf:out {
		deviate add {
			must "not (../../ippf:group[ippf:group-name = current()]/ippf:rule[not(ippf:disable)]/ippf:match[ippf:icmp])" {
				error-message "Unsupported ICMPv4 matching for outbound traffic";
			}
			must "not (../../ippf:group[ippf:group-name = current()]/ippf:rule[not(ippf:disable)]/ippf:match[ippf:icmpv6])" {
				error-message "Unsupported ICMPv6 matching for outbound traffic";
			}
			must "not (../../ippf:group[ippf:group-name = current()]/ippf:rule[not(ippf:disable)]/ippf:match/ippf:source[ippf:port])" {
				error-message "Unsupported L4 source port matching for outbound traffic";
			}
			must "not (../../ippf:group[ippf:group-name = current()]/ippf:rule[not(ippf:disable)]/ippf:match/ippf:destination[ippf:port])" {
				error-message "Unsupported L4 destination port matching for outbound traffic";
			}
		}
	}

	deviation /security:security/ippf:ip-packet-filter {
		deviate add {
			/*
			 * Ensure that the total set of rules applied inbound for IPv6
			 * do not exceed the available key space of the TCAM.
			 * We have 320 bits total, and 20 are used for fixed qualifiers.
			 */
			must "128 * (count(ippf:group[ippf:ip-version = 'ipv6' and ippf:group-name = ../ippf:interface/ippf:in]/ippf:rule[not(ippf:disable)]/ippf:match[ippf:destination/ippf:ipv6]) > 0) + " +
			     "128 * (count(ippf:group[ippf:ip-version = 'ipv6' and ippf:group-name = ../ippf:interface/ippf:in]/ippf:rule[not(ippf:disable)]/ippf:match[ippf:source/ippf:ipv6]) > 0) + " +
			     "16 * (count(ippf:group[ippf:ip-version = 'ipv6' and ippf:group-name = ../ippf:interface/ippf:in]/ippf:rule[not(ippf:disable)]/ippf:match[ippf:destination/ippf:port]) > 0) + " +
			     "16 * (count(ippf:group[ippf:ip-version = 'ipv6' and ippf:group-name = ../ippf:interface/ippf:in]/ippf:rule[not(ippf:disable)]/ippf:match[ippf:source/ippf:port or ippf:icmpv6]) > 0) + " +
			     "8 * (count(ippf:group[ippf:ip-version = 'ipv6' and ippf:group-name = ../ippf:interface/ippf:in]/ippf:rule[not(ippf:disable)]/ippf:match[ippf:protocol]) > 0) + " +
			     "8 * (count(ippf:group[ippf:ip-version = 'ipv6' and ippf:group-name = ../ippf:interface/ippf:in]/ippf:rule[not(ippf:disable)]/ippf:match[ippf:ttl]) > 0) + " +
			     "8 * (count(ippf:group[ippf:ip-version = 'ipv6' and ippf:group-name = ../ippf:interface/ippf:in]/ippf:rule[not(ippf:disable)]/ippf:match[ippf:dscp]) > 0) <= 300" {
				error-message "IPv6 input matches across all groups would exceed TCAM key space";
			}
		}
	}
}
