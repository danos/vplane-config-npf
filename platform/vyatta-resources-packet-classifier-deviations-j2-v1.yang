module vyatta-resources-packet-classifier-deviations-j2-v1 {
	namespace "urn:vyatta.com:mgmt:vyatta-resources-packet-classifier-deviations-j2:1";
	prefix pkt-class-dev-j2-v1;

	import vyatta-resources-v1 {
		prefix resources;
	}
	import vyatta-resources-packet-classifier-v1 {
		prefix pkt-class;
	}

	organization "AT&T Inc.";
	contact
		"AT&T
		 Postal: 208 S. Akard Street
		         Dallas, TX 75202, USA
		 Web: www.att.com";

	description
		"Copyright (c) 2021, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for Vyatta Generic Packet Classifier";

	revision 2021-04-16 {
		description "Initial version.";
	}

	deviation /resources:resources/pkt-class:packet-classifier/pkt-class:classifier/pkt-class:rule/pkt-class:match/pkt-class:fragment {
		deviate add {
			must "../../../pkt-class:type = 'ipv4' or
				../pkt-class:protocol/pkt-class:base/pkt-class:number = 44 or
				../pkt-class:protocol/pkt-class:base/pkt-class:name = 'ipv6-frag'" {
				error-message "IPv6 group rules that match on fragments must also match on 'ipv6-frag' protocol base";
			}
		}
	}

	deviation /resources:resources/pkt-class:packet-classifier/pkt-class:classifier/pkt-class:rule/pkt-class:match/pkt-class:protocol/pkt-class:final {
		deviate not-supported;
	}

	deviation /resources:resources/pkt-class:packet-classifier/pkt-class:classifier {
		deviate add {
			/*
			 * Ensure that the total set of rules for IPv6 does not
			 * exceed the available key space of the TCAM.
			 * We have 320 bits total, and 22 bits are used to
			 * match the target interface.
			 *
			 * Note that the below works for QoS where only one
			 * IPv6 group may be bound (via a policy filter) to
			 * one interface. For features not having this 1:1
			 * relationship, the below will need to be
			 * implemented as a check across all bound groups
			 * in the feature code.
			 */
			must "pkt-class:type = 'ipv4' or " +
			     "128 * (count(pkt-class:rule[not(pkt-class:disable)]/pkt-class:match[pkt-class:destination/pkt-class:ipv6]) > 0) + " +
			     "128 * (count(pkt-class:rule[not(pkt-class:disable)]/pkt-class:match[pkt-class:source/pkt-class:ipv6]) > 0) + " +
			     "16 * (count(pkt-class:rule[not(pkt-class:disable)]/pkt-class:match[pkt-class:destination/pkt-class:port]) > 0) + " +
			     "16 * (count(pkt-class:rule[not(pkt-class:disable)]/pkt-class:match[pkt-class:source/pkt-class:port or pkt-class:icmpv6]) > 0) + " +
			     "8 * (count(pkt-class:rule[not(pkt-class:disable)]/pkt-class:match[pkt-class:protocol]) > 0) + " +
			     "8 * (count(pkt-class:rule[not(pkt-class:disable)]/pkt-class:match[pkt-class:ttl]) > 0) + " +
			     "8 * (count(pkt-class:rule[not(pkt-class:disable)]/pkt-class:match[pkt-class:dscp]) > 0) + 22 <= 320" {
				error-message "IPv6 input matches across all groups would exceed TCAM key space";
			}
		}
	}
}
