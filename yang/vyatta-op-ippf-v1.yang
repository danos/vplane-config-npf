module vyatta-op-ippf-v1 {
	namespace "urn:vyatta.com:mgmt:vyatta-op-ippf:1";
	prefix vyatta-op-ippf-v1;

	import vyatta-opd-extensions-v1 {
		prefix opd;
	}
	import vyatta-op-show-v1 {
		prefix op-show;
	}
	import vyatta-op-show-security-v1 {
		prefix op-show-security;
	}
	import vyatta-op-clear-v1 {
		prefix op-clear;
	}
	import vyatta-op-clear-security-v1 {
		prefix op-clear-security;
	}
	import vyatta-fw-types-v1 {
		prefix fw-types;
	}

	organization "AT&T Inc.";
	contact
		"AT&T
		 Postal: 208 S. Akard Street
		         Dallas, TX 75202, USA
		 Web: www.att.com";

	description
		"Copyright (c) 2019-2020, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for Vyatta IP Packet Filter operation mode commands.";

	revision 2020-11-02 {
		description "Permanently enabled ip-packet-filter. " +
			"Removed import of vyatta-ippf-v1.yang";
	}

	revision 2020-05-08 {
		description "Add Egress IP Packet Filter support.";
	}

	revision 2019-06-20 {
		description "Initial revision.";
	}

	opd:augment /op-show:show/op-show-security:security {
		opd:command ip-packet-filter {
			opd:help "Show IP packet filter";

			opd:command statistics {
				opd:help "Show IP packet filter statistics";
				opd:inherit "" {
					opd:on-enter "vyatta-ippf-op $@";
				}
				opd:repeatable true;

				opd:option interface {
					opd:help "Show IPPF statistics for an interface";
					opd:allowed "allowed-nodes security ip-packet-filter interface";
					type string {
						opd:help "Interface name";
					}
				}
				opd:option direction {
					opd:help "Show IPPF statistics for a direction";
					type enumeration {
						opd:help "Direction";
						enum "in" {
							description "Show statistics for inbound traffic";
							opd:help    "Show statistics for inbound traffic";
						}
						enum "out" {
							description "Show statistics for outbound traffic";
							opd:help    "Show statistics for outbound traffic";
						}
					}
				}
				opd:option group {
					opd:help "Show IPPF statistics for a group";
					opd:allowed "allowed-nodes security ip-packet-filter group";
					type string {
						opd:help "Group";
					}
				}
				opd:option rule {
					opd:help "Show IPPF statistics for a rule";
					type fw-types:rule-number {
						opd:help "Rule number";
					}
				}
				opd:option action {
					opd:help "Show IPPF statistics for an action";
					type enumeration {
						opd:help "Action";
						enum "accept" {
							description "Show statistics for accepted traffic";
							opd:help    "Show statistics for accepted traffic";
						}
						enum "drop" {
							description "Show statistics for dropped traffic";
							opd:help    "Show statistics for dropped traffic";
						}
						enum "punt" {
							description "Show statistics for punted traffic";
							opd:help    "Show statistics for punted traffic";
						}
						enum "reject" {
							description "Show statistics for rejected traffic";
							opd:help    "Show statistics for rejected traffic";
						}
					}
				}
			} /* statistics */
		} /* ippf */
	} /* show */

	opd:augment /op-clear:clear/op-clear-security:security {
		opd:command ip-packet-filter {
			opd:help "Clear IP packet filter";

			opd:command statistics {
				opd:help "Clear IP packet filter statistics";
				opd:inherit "" {
					opd:on-enter "vyatta-ippf-op $@";
				}

				opd:option interface {
					opd:help "Clear IPPF statistics for the specified interface";
					opd:allowed "allowed-nodes security ip-packet-filter interface";

					type string {
						opd:help "Interface name";
					}

					opd:option direction {
						opd:help "Clear IPPF statistics for the specified direction";
						type enumeration {
							opd:help "Direction";
							enum "in" {
								description "Clear statistics for inbound traffic";
								opd:help    "Clear statistics for inbound traffic";
							}
							enum "out" {
								description "Clear statistics for outbound traffic";
								opd:help    "Clear statistics for outbound traffic";
							}
						}

						opd:option group {
							opd:help "Clear IPPF statistics for the specified group";
							opd:allowed "allowed-nodes security ip-packet-filter group";
							type string {
								opd:help "Group";
							}
						}
					}
				}
			} /* statistics */
		} /* ippf */
	} /* clear */
}
