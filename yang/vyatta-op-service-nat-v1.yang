module vyatta-op-service-nat-v1 {
	namespace "urn:vyatta.com:mgmt:vyatta-op-service-nat:1";
	prefix vyatta-op-service-nat-v1;

	import vyatta-opd-extensions-v1 {
		prefix opd;
	}
	import vyatta-op-show-v1 {
		prefix show;
	}
	import vyatta-op-show-log-v1 {
		prefix show-log;
	}
	import vyatta-op-clear-v1 {
		prefix clear;
	}
	import vyatta-op-npf-types-v1 {
		prefix op-npf-types;
	}

	organization "AT&T Inc.";
	contact
		"AT&T
		 Postal: 208 S. Akard Street
		         Dallas, TX 75202, USA
		 Web: www.att.com";

	description
		"Copyright (c) 2017-2021, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for NAT-related operation mode commands.";

	revision 2020-02-08 {
		description "Escalate privileges of show/clear nat commands.";
	}

	revision 2018-06-25 {
		description "Extend options for clearing statistics.";
	}

	revision 2018-01-24 {
		description "Update logging to get info from journalctl";
	}

	revision 2017-12-15 {
		description "Conversion from node files.";
	}

	opd:augment /show:show {

		opd:command nat {
			opd:help "Show NAT information";
			opd:on-enter "vyatta-dp-npf-show-rules all: snat dnat";
			opd:inherit "" {
				opd:privileged true;
			}

			opd:command destination {
				opd:help "Show destination NAT information";
				opd:on-enter "vyatta-dp-npf-show-rules all: dnat";

				opd:command rules {
					opd:help "Show destination NAT rules";
					opd:on-enter "vyatta-dp-npf-show-rules all: dnat";
				}

				opd:command statistics {
					opd:help "Show destination NAT statistics";
					opd:on-enter "vyatta-dp-npf-show-rules --variant=stats all: dnat";
				}

				opd:command translations {
					opd:help "Show destination NAT translations";
					opd:on-enter "vyatta-dp-npf-show-nat-trans destination";
				}
			}

			opd:command source {
				opd:help "Show source NAT information";
				opd:on-enter "vyatta-dp-npf-show-rules all: snat";

				opd:command rules {
					opd:help "Show source NAT rules";
					opd:on-enter "vyatta-dp-npf-show-rules all: snat";
				}

				opd:command statistics {
					opd:help "Show source NAT statistics";
					opd:on-enter "vyatta-dp-npf-show-rules --variant=stats all: snat";
				}

				opd:command translations {
					opd:help "Show source NAT translations";
					opd:on-enter "vyatta-dp-npf-show-nat-trans source";
				}
			}
		}
	}

	opd:augment /show:show/show-log:log {

		opd:command nat {
			opd:help "Show log for Network Address Translation (NAT)";
			opd:on-enter 'npf-show-logs "[sd]nat rule .*:[0-9]+ "';
		}
	}

	opd:augment /clear:clear {

		opd:command nat {
			opd:help "Clear NAT statistics";
			opd:on-enter "vyatta-dp-npf-clear nat";
			opd:inherit "" {
				opd:privileged true;
			}

			opd:command source {
				opd:help "Clear source NAT statistics";
				opd:on-enter 'vyatta-dp-npf-clear snat44';

				opd:option interface {
					opd:help "Clear statistics for the specified interface";
					type op-npf-types:op-ifname;
					opd:allowed "vyatta-interfaces.pl --show=all";
					opd:on-enter 'vyatta-dp-npf-clear snat44 interface $5';

					opd:option rule {
						opd:help "Clear statistics for specified rule";
						type op-npf-types:op-rule-number;
						opd:allowed "allowed-nodes service nat source rule";
						opd:on-enter 'vyatta-dp-npf-clear snat44 interface $5 rule $7';
					}
				}
			}

			opd:command destination {
				opd:help "Clear destination NAT statistics";
				opd:on-enter 'vyatta-dp-npf-clear dnat44';

				opd:option interface {
					opd:help "Clear statistics for the specified interface";
					type op-npf-types:op-ifname;
					opd:allowed "vyatta-interfaces.pl --show=all";
					opd:on-enter 'vyatta-dp-npf-clear dnat44 interface $5';

					opd:option rule {
						opd:help "Clear statistics for specified rule";
						type op-npf-types:op-rule-number;
						opd:allowed "allowed-nodes service nat destination rule";
						opd:on-enter 'vyatta-dp-npf-clear dnat44 interface $5 rule $7';
					}
				}
			}
		}
	}
}
