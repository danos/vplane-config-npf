module vyatta-op-policy-pbr-v1 {
	namespace "urn:vyatta.com:mgmt:vyatta-op-policy-pbr:1";
	prefix vyatta-op-policy-pbr-v1;

	import vyatta-opd-extensions-v1 {
		prefix opd;
	}
	import vyatta-op-show-v1 {
		prefix show;
	}
	import vyatta-op-show-log-v1 {
		prefix show-log;
	}
	import vyatta-op-clear-v1 {
		prefix clear;
	}
	import vyatta-op-npf-types-v1 {
		prefix op-npf-types;
	}

	organization "AT&T Inc.";
	contact
		"AT&T
		 Postal: 208 S. Akard Street
		         Dallas, TX 75202, USA
		 Web: www.att.com";

	description
		"Copyright (c) 2017-2019, 2021, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for PBR-related operation mode commands.";

	revision 2021-02-08 {
		description "Escalate privileges of show/clear policy";
	}

	revision 2018-06-25 {
		description "Extend options for clearing statistics.";
	}

	revision 2018-01-25 {
		description "Add show log policy commands.";
	}

	revision 2017-09-15 {
		description "Conversion from node files.";
	}

	opd:augment /show:show {

		opd:command policy {
			opd:help "Show PBR policy details";
			opd:on-enter "vyatta-dp-npf-show-rules all: pbr";
			opd:privileged true;

			opd:command route {
				opd:help "Show dataplane PBR information";
				opd:on-enter "vyatta-dp-npf-show-rules all: pbr";
				opd:inherit "" {
					opd:privileged true;
				}

				opd:command table {
					opd:help "Show dataplane PBR policy table";
					opd:on-enter "vyatta-dp-npf-show-rules --variant=pbr-table all: pbr";
				}

				opd:argument name {
					opd:help "Show dataplane PBR information";
					opd:allowed "vyatta-interfaces.pl --show all --skip=lo";
					opd:on-enter "vyatta-dp-npf-show-rules interface:$4 pbr";
					type op-npf-types:op-ifname;
				}
			}
		}
	}

	opd:augment /show:show/show-log:log {

		opd:command policy {
			opd:help "Show log for PBR";

			opd:option route {
				opd:help "Show log for the specified PBR group";
				type op-npf-types:op-ruleset-name;
				opd:allowed "allowed-nodes policy route pbr";
				opd:on-enter 'npf-show-logs "pbr rule $5:[0-9]+ "';
				opd:option rule {
					opd:help "Show log for a rule in the specified PBR group";
					type op-npf-types:op-rule-number;
					opd:allowed "allowed-nodes policy route pbr ${COMP_WORDS[4]} rule";
					opd:on-enter 'npf-show-logs "pbr rule $5:$7 "';
				}
			}
		}
	}

	opd:augment /clear:clear {

		opd:command policy {
			opd:help "clear statistics for policy based routing";
			opd:on-enter "vyatta-dp-npf-clear pbr";
			opd:privileged true;

			opd:option interface {
				opd:help "Clear statistics for the specified interface";
				type op-npf-types:op-ifname;
				opd:allowed "vyatta-interfaces.pl --show=all --includes='policy route pbr'";
				opd:on-enter 'vyatta-dp-npf-clear pbr interface $4';
				opd:inherit "" {
					opd:privileged true;
				}

				opd:option name {
					opd:help "Clear statistics for specified ruleset";
					type op-npf-types:op-ruleset-name;
					opd:allowed "allowed-nodes `vyatta-interfaces.pl --conf-line --dev=${COMP_WORDS[3]}` policy route pbr";

					opd:on-enter 'vyatta-dp-npf-clear pbr interface $4 name $6';

					opd:option rule {
						opd:help "Clear statistics for specified rule";
						type op-npf-types:op-rule-number;
						opd:allowed "allowed-nodes policy route pbr ${COMP_WORDS[5]} rule";
						opd:on-enter 'vyatta-dp-npf-clear pbr interface $4 name $6 rule $8';
					}
				}
			}
		}
	}
}
