module vyatta-ippf-v1 {
	namespace "urn:vyatta.com:mgmt:vyatta-ippf:1";
	prefix vyatta-ippf-v1;

	import vyatta-security-v1 {
		prefix security;
	}
	import configd-v1 {
		prefix configd;
	}
	import vyatta-fw-types-v1 {
		prefix fw-types;
	}
	import vyatta-types-v1 {
		prefix vy-types;
	}
	import vyatta-dscp-v1 {
		prefix dscp;
	}
	import ietf-inet-types {
		prefix inet;
	}
	import vyatta-npf-v1 {
		prefix npf;
	}

	organization "AT&T Inc.";
	contact
		"AT&T
		 Postal: 208 S. Akard Street
			 Dallas, TX 75202, USA
		 Web: www.att.com";

	description
		"Copyright (c) 2019-2021, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for Vyatta IP Packet Filter";

	revision 2021-04-16 {
		description "Updated error messages related to 'protocol final',
			     as it is not supported on some platforms.
			     Update for GPC use.";
	}

	revision 2020-10-23 {
		description "Added counter type option 'auto-per-action'.
			     Added 'name' leaf in the statistics output for carrying 'auto-per-action' counters.
			     Permanently enabled ip-packet-filter.
			     Don't allow matching L4 fields if matching fragments.";
	}

	revision 2020-05-08 {
		description "Added Egress IP Packet Filter support.
			     Updated 'interface:in' form to use leafref for validation";
	}

	revision 2020-04-15 {
		description
			"Add additional match criteria:
			  - TTL
			  - DSCP
			  - ICMP (IPv4) type/code
			  - ICMPv6 type/code
			  - ICMPv6 class
			  - L4 ports
			";
	}

	revision 2020-04-03 {
		description "Added 'ipv6-frag' matching option in 'protocol base'. " +
			    "Added help/description for 'protocol base/final'.";
	}

	revision 2019-06-20 {
		description "Initial revision.";
	}

	feature ip-packet-filter {
		description "IP Packet Filter support";
	}

	grouping ippf-address-group {
		description "An IPv4 or IPv6 host address, prefix or port";
		container ipv4 {
			description  "Match IPv4";
			configd:help "Match IPv4";
			presence "IPv4 match criteria; mandatory child nodes when configured";
			must "count( prefix | host ) = 1" {
				error-message "Configure either 'prefix' or 'host'";
			}
			must "not (../../../../ip-version = 'ipv6')" {
				error-message "'match ipv4' is not available in IPv6 groups";
			}
			must "not (../../../../type = 'ipv6')" {
				error-message "'match ipv4' is not available in IPv6 classifiers";
			}
			leaf prefix {
				description  "Match an IPv4 prefix";
				configd:help "Match an IPv4 prefix";
				type vy-types:ipv4-prefix {
					configd:help "IPv4 prefix to match";
					configd:normalize "normalize ipv4-prefix";
					configd:pattern-help "IPv4 prefix, /1 through /31";
					pattern '.*/(([1-9])|([1-2][0-9])|(3[0-1]))' {
						error-message "Must be <IPv4-address>/<x>, where <x> is 1 through 31";
					}
				}
			}
			leaf host {
				description  "Match an IPv4 address";
				configd:help "Match an IPv4 address";
				type vy-types:ipv4-address {
					configd:help "IPv4 address to match";
					configd:normalize "normalize ipv4";
				}
			}
		}
		container ipv6 {
			description  "Match IPv6";
			configd:help "Match IPv6";
			presence "IPv6 match criteria; mandatory child nodes when configured";
			must "count( prefix | host ) = 1" {
				error-message "Configure either 'prefix' or 'host'";
			}
			must "not (../../../../ip-version = 'ipv4')" {
				error-message "'match ipv6' is not available in IPv4 groups";
			}
			must "not (../../../../type = 'ipv4')" {
				error-message "'match ipv6' is not available in IPv4 classifiers";
			}
			must "not (../ipv4)" {
				error-message "Configure either 'ipv4' or 'ipv6'";
			}
			leaf prefix {
				description  "Match an IPv6 prefix";
				configd:help "Match an IPv6 prefix";
				type vy-types:ipv6-prefix {
					configd:help "IPv6 prefix to match";
					configd:normalize "normalize ipv6-prefix";
					configd:pattern-help "IPv6 prefix, /1 through /127";
					pattern '.*/(([1-9])|([1-9][0-9])|(1[0-1][0-9])|(12[0-7]))' {
						error-message "Must be <IPv6-address>/<x>, where <x> is 1 through 127";
					}
				}
			}
			leaf host {
				description  "Match an IPv6 address";
				configd:help "Match an IPv6 address";
				type vy-types:ipv6-address {
					configd:help "IPv6 address to match";
				}
			}
		}
		container port {
			description  "Match port";
			configd:help "Match port";
			must "not (../port) or not ((../../fragment = 'any') or (../../protocol/base/name = 'ipv6-frag') or (../../protocol/base/number = 44))" {
				error-message "Fragmentation matching cannot be performed at the same time as Layer 4 packet matching";
			}
			/* If a port is specified, then we need to specify a protocol supporting ports */
			must "not (../port) or ((../../protocol/final) and not (../../protocol/base)) or
			       ((../../protocol/base/name = 'tcp') or (../../protocol/base/number = 6) or
				(../../protocol/base/name = 'udp') or (../../protocol/base/number = 17) or
				(../../protocol/base/name = 'udplite') or (../../protocol/base/number = 136) or
				(../../protocol/base/name = 'sctp') or (../../protocol/base/number = 132) or
				(../../protocol/base/name = 'dccp') or (../../protocol/base/number = 33))" {
				error-message "Configure a 'match protocol base [name|number]' which supports ports (tcp(6), udp(17), udplite(136), sctp(132), dccp(33))";
			}
			must "not (../port) or ((../../protocol/base) and not (../../protocol/final)) or
			       ((../../protocol/final/name = 'tcp') or (../../protocol/final/number = 6) or
				(../../protocol/final/name = 'udp') or (../../protocol/final/number = 17) or
				(../../protocol/final/name = 'udplite') or (../../protocol/final/number = 136) or
				(../../protocol/final/name = 'sctp') or (../../protocol/final/number = 132) or
				(../../protocol/final/name = 'dccp') or (../../protocol/final/number = 33))" {
				error-message "Configure a 'match protocol final [name|number]' which supports ports (tcp(6), udp(17), udplite(136), sctp(132), dccp(33))";
			}
			leaf-list number {
				description  "Port number to match";
				configd:help "Port number to match";
				type vy-types:port;
				max-elements 1;
			}
		}
	}

	grouping ippf-protocol {
		description "Definition of a layer 4 protocol, either by name or by number";
		leaf name {
			description  "IP L4 header protocol name to match";
			configd:help "IP L4 header protocol name to match";
			type enumeration {
				enum "tcp" {
					description  "Match TCP packets (protocol 6)";
					configd:help "Match TCP packets (protocol 6)";
				}
				enum "udp" {
					description  "Match UDP packets (protocol 17)";
					configd:help "Match UDP packets (protocol 17)";
				}
				enum "udplite" {
					description  "Match UDPlite packets (protocol 136)";
					configd:help "Match UDPlite packets (protocol 136)";
				}
				enum "dccp" {
					description  "Match DCCP packets (protocol 33)";
					configd:help "Match DCCP packets (protocol 33)";
				}
				enum "sctp" {
					description  "Match SCTP packets (protocol 132)";
					configd:help "Match SCTP packets (protocol 132)";
				}
				enum "icmp" {
					description  "Match ICMP packets (protocol 1)";
					configd:help "Match ICMP packets (protocol 1)";
				}
				enum "igmp" {
					description  "Match IGMP packets (protocol 2)";
					configd:help "Match IGMP packets (protocol 2)";
				}
				enum "gre" {
					description  "Match GRE packets (protocol 47)";
					configd:help "Match GRE packets (protocol 47)";
				}
				enum "ipv6-icmp" {
					description  "Match IPv6 ICMP packets (protocol 58)";
					configd:help "Match IPv6 ICMP packets (protocol 58)";
				}
				enum "esp" {
					description  "Match IPSEC ESP packets (protocol 50)";
					configd:help "Match IPSEC ESP packets (protocol 50)";
				}
				enum "ipv6-frag" {
					description  "Match IPv6 fragment packets (protocol 44)";
					configd:help "Match IPv6 fragment packets (protocol 44)";
				}
			}
		}
		leaf number {
			description  "IP L4 header protocol number to match";
			configd:help "IP L4 header protocol number to match";
			type uint32 {
				range 0..255 {
					error-message "Must be between 0 and 255";
				}
			}
		}
	}

	grouping ippf-match {
		description "Definition of a single IP packet filter match rule";
		container dscp {
			description  "DSCP parameters";
			configd:help "DSCP parameters";
			leaf name {
				description  "DSCP name to match in IP header";
				configd:help "DSCP name to match in IP header";
				must "not (../value)" {
					error-message "Configure either 'name' or 'value', not both";
				}
				type dscp:dscp-name;
			}
			leaf value {
				description  "DSCP value to match in IP header";
				configd:help "DSCP value to match in IP header";
				type inet:dscp;
			}
		}
		container ttl {
			description  "Match TTL in IPv4 header or Hop Count in IPv6 header";
			configd:help "Match TTL in IPv4 header or Hop Count in IPv6 header";
			leaf equals {
				description  "TTL value to match";
				configd:help "TTL value to match";
				type uint32 {
					range "1 | 255";
					configd:help "TTL to match";
				}
			}
		}
		leaf fragment {
			description  "Match fragments";
			configd:help "Match fragments";
			type enumeration {
				enum "any" {
					description  "Match any fragment";
					configd:help "Match any fragment";
				}
			}
		}
		container protocol {
			description  "Protocol parameters";
			configd:help "Protocol parameters";
			container base {
				description  "Match on protocol/next-header in IPv4/v6 header";
				configd:help "Match on protocol/next-header in IPv4/v6 header";
				uses ippf-protocol;
				presence "Base protocol match criteria; mandatory child nodes when configured";
				must "count( name | number ) = 1" {
					error-message "Configure either 'name' or 'number'";
				}
			}
			container final {
				description  "Match on protocol of final header";
				configd:help "Match on protocol of final header";
				uses ippf-protocol;
				presence "Final protocol match criteria; mandatory child nodes when configured";
				must "count( name | number ) = 1" {
					error-message "Configure either 'name' or 'number'";
				}
			}
		}
		container source {
			description  "Source parameters";
			configd:help "Source parameters";
			uses ippf-address-group;
		}
		container destination {
			description  "Destination parameters";
			configd:help "Destination parameters";
			uses ippf-address-group;
		}
		container icmp {
			description  "ICMP for IPv4";
			configd:help "ICMP for IPv4";
			must "not (../icmp) or not (../../../ip-version = 'ipv6')" {
				error-message "'match icmp' is not available in IPv6 groups";
			}
			must "not (../icmp) or not (../../../type = 'ipv6')" {
				error-message "'match icmp' is not available in IPv6 classifiers";
			}
			must "not (../icmp) or (../protocol/base) or (../protocol/final)" {
				error-message "'match icmp' requires 'protocol base' or (if supported) 'protocol final'";
			}
			must "not (../icmp) or not (../protocol/base) or
			      (../protocol/base/name = 'icmp') or (../protocol/base/number = 1)" {
				error-message "'match icmp' can only be used if 'protocol base' is ICMP or not set";
			}
			must "not (../icmp) or not (../protocol/final) or
			      (../protocol/final/name = 'icmp') or (../protocol/final/number = 1)" {
				error-message "'match icmp' can only be used if 'protocol final' is ICMP or not set";
			}
			must "not (../icmp) or not ((../fragment = 'any') or (../protocol/base/name = 'ipv6-frag') or (../protocol/base/number = 44) or (../protocol/final/name = 'ipv6-frag') or (../protocol/final/number = 44))" {
				error-message "Fragmentation matching cannot be performed at the same time as Layer 4 packet matching";
			}
			must "not (../icmp) or count( name | type ) = 1" {
				error-message "Configure either 'name' or 'type', not both";
			}
			uses npf:rule-icmp-numeric;
			leaf name {
				description  "Choose a type (and optional code) by name";
				configd:help "Choose a type (and optional code) by name";
				type fw-types:icmpv4-symbolic;
			}
		}
		container icmpv6 {
			description  "ICMP for IPv6";
			configd:help "ICMP for IPv6";
			must "not (../icmpv6) or not (../../../ip-version = 'ipv4')" {
				error-message "'match icmpv6' is not available in IPv4 groups";
			}
			must "not (../icmpv6) or not (../../../type = 'ipv4')" {
				error-message "'match icmpv6' is not available in IPv4 classifiers";
			}
			must "not (../icmpv6) or (../protocol/base) or (../protocol/final)" {
				error-message "'match icmpv6' requires 'protocol base' or (if supported) 'protocol final'";
			}
			must "not (../icmpv6) or not (../protocol/base) or
			      (../protocol/base/name = 'ipv6-icmp') or (../protocol/base/number = 58)" {
				error-message "'match icmpv6' can only be used if 'protocol base' is ICMPv6 or not set";
			}
			must "not (../icmpv6) or not (../protocol/final) or
			      (../protocol/final/name = 'ipv6-icmp') or (../protocol/final/number = 58)" {
				error-message "'match icmpv6' can only be used if 'protocol final' is ICMPv6 or not set";
			}
			must "not (../icmpv6) or not ((../fragment = 'any') or (../protocol/base/name = 'ipv6-frag') or (../protocol/base/number = 44) or (../protocol/final/name = 'ipv6-frag') or (../protocol/final/number = 44))" {
				error-message "Fragmentation matching cannot be performed at the same time as Layer 4 packet matching";
			}
			must "not (../icmpv6) or count( name | type | class ) = 1" {
				error-message "Configure exactly one of 'name', 'type', or 'class'";
			}
			uses npf:rule-icmp-numeric;
			leaf name {
				description  "Choose a type (and optional code) by name";
				configd:help "Choose a type (and optional code) by name";
				type fw-types:icmpv6-symbolic;
			}
			leaf class {
				description  "Match ICMPv6 class";
				configd:help "Match ICMPv6 class";
				type enumeration {
					enum "info" {
						description  "Match ICMPv6 info packets";
						configd:help "Match ICMPv6 info packets";
					}
					enum "error" {
						description  "Match ICMPv6 error packets";
						configd:help "Match ICMPv6 error packets";
					}
				}
			}
		}
	}

	grouping ippf-action {
		description "Definition of an IP packet filter rule action";
		leaf accept {
			description  "Accept matching packets";
			configd:help "Accept matching packets";
			type empty;
		}
		leaf drop {
			description  "Drop matching packets";
			configd:help "Drop matching packets";
			type empty;
		}
	}

	augment /security:security {
		description "Top-level IP packet filter command";
		container ip-packet-filter {
			description  "IP packet filter";
			configd:help "IP packet filter";
			configd:validate "validate-fw-groups --variant ippf";
			configd:validate "validate-ippf";
			configd:end "end-ippf-ruleset --commit";
			presence "IP packet filter criteria; mandatory child nodes when configured";
			list group {
				description  "IP packet filter group";
				configd:help "IP packet filter group";
				configd:end "end-ippf-ruleset --group $VAR(@)";
				key "group-name";
				min-elements 1;
				leaf group-name {
					description  "Group name";
					configd:help "Group name";
					type vy-types:alpha-numeric {
						configd:help "Group name";
					}
				}
				leaf description {
					description  "Group description";
					configd:help "Group description";
					type string;
				}
				leaf ip-version {
					description  "IP version for this group";
					configd:help "IP version for this group";
					mandatory true;
					type enumeration {
						enum "ipv4" {
							description  "Group only applies to IPv4 traffic";
							configd:help "Group only applies to IPv4 traffic";
						}
						enum "ipv6" {
							description  "Group only applies to IPv6 traffic";
							configd:help "Group only applies to IPv6 traffic";
						}
					}
				}
				leaf type {
					description
						"Reserved for compatibility with GPC.
						 The IPPF match container is shared by IPPF and GPC.
						 This has been created such that the address family specific
						 must statements within IPPF may refer to either ip-version
						 (as used by IPPF) or type (as used by GPC).";
					type string;
					status obsolete;
				}
				container counters {
					description  "Configure counters";
					configd:help "Configure counters";
					presence "Group counter criteria; mandatory child nodes when configured";
					leaf sharing {
						description  "Configured counter sharing";
						configd:help "Configured counter sharing";
						mandatory true;
						type enumeration {
							enum "per-interface" {
								description  "Unique counter applied to multiple interfaces";
								configd:help "Unique counter applied to multiple interfaces";
							}
						}
					}
					leaf-list count {
						description  "Configure what to count";
						configd:help "Configure what to count";
						min-elements 1;
						type enumeration {
							enum "packets" {
								description  "Count packets";
								configd:help "Count packets";
							}
						}
					}
					container type {
						description  "Configure counter type";
						configd:help "Configure counter type";
						presence "Counter type criteria; mandatory child nodes when configured";
						must "count(*) = 1" {
							error-message "'counter type' must be configured";
						}
						leaf auto-per-rule {
							description  "Auto per rule";
							configd:help "Auto per rule";
							type empty;
						}
						container auto-per-action {
							description  "Auto per action";
							configd:help "Auto per action";
							presence "Configure all actions";
							container action {
								description  "Configure actions";
								configd:help "Configure actions";
								uses ippf-action;
								must "count(accept | drop) <= 1" {
									error-message "Cannot specify both 'accept' and 'drop'";
								}
							}
						}
					}
				}
				list rule {
					description  "Rule number";
					configd:help "Rule number";
					min-elements 1;
					must "action or disable" {
						error-message "Either configure an 'action', or 'disable' this rule";
					}
					key "number";
					leaf number {
						description  "rule number";
						configd:help "rule number";
						type fw-types:rule-number;
					}
					leaf disable {
						description  "Disable rule";
						configd:help "Disable rule";
						type empty;
					}
					leaf description {
						description  "Rule description";
						configd:help "Rule description";
						type string;
					}
					container match {
						description  "Configure match criteria";
						configd:help "Configure match criteria";
						uses ippf-match;
					}
					container action {
						description  "Configure actions";
						configd:help "Configure actions";
						uses ippf-action;
						must "count(accept | drop) = 1" {
							error-message "Configure either 'accept' or 'drop'";
						}
					}
				}
			}
			list interface {
				description  "Interface for IP packet filter";
				configd:help "Interface for IP packet filter";
				configd:allowed "vyatta-interfaces.pl --show all";
				configd:end "end-ippf-ruleset --interface $VAR(@)";
				must "in | out" {
					error-message "Configure at least one group for input or output";
				}
				/* There's a limit of one group per address-family.
				 * Here we ensure there are no more than two groups.
				 * Until nested predicates are supported
				 * a higher level configd:validate ensures they have different AFs.
				 */
				must "count(in) <= 2" {
					error-message "Configure only one group per address-family";
				}
				must "count(out) <= 2" {
					error-message "Configure only one group per address-family";
				}
				key "interface-name";
				leaf interface-name {
					description  "Interface name";
					configd:help "Interface name";
					type vy-types:interface-ifname;
				}
				leaf-list in {
					description  "Input group";
					configd:help "Input group";
					ordered-by "user";
					type leafref {
						path "/security:security/ip-packet-filter/group/group-name";
					}
				}
				leaf-list out {
					description  "Output group";
					configd:help "Output group";
					ordered-by "user";
					type leafref {
						path "/security:security/ip-packet-filter/group/group-name";
					}
				}
			}
		}
	}

	rpc get-statistics {
		description "Get IP Packet Filter statistics. The inputs specify optional filters to limit the returned statistics";
		configd:call-rpc "vyatta-ippf-rpc --show";

		input {
			leaf-list interfaces {
				description "Get statistics for the named interfaces";
				type string;
			}
			leaf-list directions {
				description "Get statistics for the named directions";
				type string;
			}
			leaf-list groups {
				description "Get statistics for the named groups";
				type string;
			}
			leaf-list rules {
				description "Get statistics for the numbered rules";
				type uint32;
			}
			leaf-list actions {
				description "Get statistics for the named actions";
				type string;
			}
		}
		output {
			list statistics {
				key row;
				leaf row {
					description "Row number";
					type uint32;
				}
				leaf interface {
					description "Interface name";
					type string;
				}
				leaf direction {
					description "The group direction";
					type string;
				}
				leaf group {
					description "The group name";
					type string;
				}
				leaf rule {
					description "The rule number";
					type uint32;
				}
				leaf name {
					description "The counter name";
					type string;
				}
				leaf action {
					description "The group action";
					type string;
				}
				container hardware {
					leaf packets {
						description "Count of packets matching the hardware rule";
						type uint64;
					}
					leaf bytes {
						description "Count of bytes matching the hardware rule";
						type uint64;
					}
				}
				container software {
					leaf packets {
						description "Count of packets matching the software rule";
						type uint64;
					}
					leaf bytes {
						description "Count of bytes matching the software rule";
						type uint64;
					}
				}
			}
		}
	}

	rpc clear-statistics {
		description "Clear IP Packet Filter statistics. The inputs specify optional filters to limit the cleared statistics";
		configd:call-rpc "vyatta-ippf-rpc --clear";
		input {
			leaf interface {
				description "Clear statistics for the named interface";
				type string;
			}
			leaf direction {
				description "Clear statistics for the named direction";
				type string;
			}
			leaf group {
				description "Clear statistics for the named group";
				type string;
			}
			leaf rule {
				description "Clear statistics for the numbered rule";
				type uint32;
			}
			leaf action {
				description "Clear statistics for the named action";
				type string;
			}
		}
		/* This RPC has no output */
	}
}
