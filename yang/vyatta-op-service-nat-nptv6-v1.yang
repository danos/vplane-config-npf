module vyatta-op-service-nat-nptv6-v1 {
	namespace "urn:vyatta.com:mgmt:vyatta-op-service-nat-nptv6:1";
	prefix vyatta-op-service-nat-nptv6-v1;

	import vyatta-opd-extensions-v1 {
		prefix opd;
	}
	import vyatta-op-show-v1 {
		prefix show;
	}
	import vyatta-op-service-nat-v1 {
		prefix nat;
	}
	import vyatta-op-npf-types-v1 {
		prefix op-npf-types;
	}

	organization "AT&T Inc.";
	contact
		"AT&T
		 Postal: 208 S. Akard Street
		         Dallas, TX 75202, USA
		 Web: www.att.com";

	description
		"Copyright (c) 2018-2019, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for NPTv6-related operation mode commands.";

	revision 2018-07-04 {
		description "Initial revision.";
	}

	opd:augment /show:show/nat:nat {

		opd:command nptv6 {
			opd:help "Show IPv6 Network Prefix Translator information";

			opd:command rules {
				opd:help "Show NPTv6 rules";
				opd:on-enter "vyatta-dp-npf-show-nptv6";

				opd:option interface {
					opd:help "Show NPTv6 rules for the specified interface";
					type op-npf-types:op-ifname;
					opd:allowed "vyatta-interfaces.pl --show=all";
					opd:on-enter "vyatta-dp-npf-show-nptv6 $6";

					opd:option name {
						opd:help "Show NPTv6 rule for the specified interface & name";
						type op-npf-types:op-ruleset-name;
						opd:allowed "allowed-nodes service nat nptv6 name";
						opd:on-enter "vyatta-dp-npf-show-nptv6 $6 $8";
					}
				}
			}

			opd:command statistics {
				opd:help "Show NPTv6 statistics";
				opd:on-enter "vyatta-dp-npf-show-nptv6 --variant=stats";

				opd:option interface {
					opd:help "Show NPTv6 stats for the specified interface";
					type op-npf-types:op-ifname;
					opd:allowed "vyatta-interfaces.pl --show=all";
					opd:on-enter "vyatta-dp-npf-show-nptv6 --variant=stats $6";

					opd:option name {
						type op-npf-types:op-ruleset-name;
						opd:help "Show NPTv6 stats for the specified interface & name";
						opd:allowed "allowed-nodes service nat nptv6 name";
						opd:on-enter "vyatta-dp-npf-show-nptv6 --variant=stats $6 $8";
					}
				}
			}
		}
	}
}
