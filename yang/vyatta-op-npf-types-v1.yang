module vyatta-op-npf-types-v1 {
	namespace "urn:vyatta.com:mgmt:vyatta-op-npf-types:1";
	prefix vyatta-op-npf-types-v1;

	import vyatta-opd-extensions-v1 {
		prefix opd;
	}

	organization "AT&T Inc.";
	contact
		"AT&T
		 Postal: 208 S. Akard Street
		         Dallas, TX 75202, USA
		 Web: www.att.com";

	description
		"Copyright (c) 2018-2020, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for NPF operation mode types.";

	revision 2020-05-12 {
		description "Added originate firewall support.";
	}

	revision 2019-04-05 {
		description "Added type op-group-name.";
	}

	revision 2018-06-28 {
		description "Initial revision.";
	}

	typedef op-alpha-numeric {
		type string {
			pattern '[0-9A-Za-z][-_0-9A-Za-z]*' {
				error-message "Only alpha-numeric name, with non-leading - or _ allowed";
			}
		}
	}

	typedef op-ruleset-name {
		type op-alpha-numeric {
			opd:pattern-help "<ruleset-name>";
		}
		opd:help "Name of the ruleset";
	}

	typedef op-group-name {
		type op-alpha-numeric {
			pattern '.*[-_A-Za-z].*';       // At least 1 non digit
		}
		opd:help "Name of the group";
	}

	typedef op-zone-name {
		type op-alpha-numeric {
			opd:pattern-help "<zone>";
		}
		opd:help "Name of the zone";
	}

	typedef op-rule-number {
		type uint32 {
			opd:pattern-help "<rule-number>";
			range 1..9999;
			opd:help "Rule number to select";
		}
	}

	typedef op-ifname {
		// NB: accepts the vif extension to the name
		type string {
			opd:pattern-help "<interface>";
			pattern '[A-Za-z][-_.0-9A-Za-z]*' {
				error-message "Only alpha-numeric name, with non-leading . - or _ allowed";
			}
			opd:help "Name of an interface";
		}
	}

	typedef op-direction {
		type string {
			opd:pattern-help "<direction>";
			pattern '(in|out|l2|local|originate)' {
				error-message "Must be: in, out, l2, local or originate";
			}
			opd:help "Traffic direction to select";
		}
	}
}
