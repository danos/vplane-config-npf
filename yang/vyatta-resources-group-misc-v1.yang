submodule vyatta-resources-group-misc-v1 {
	belongs-to vyatta-resources-group-v1 {
		prefix resources-group;
	}

	import vyatta-types-v1 {
		prefix types;
	}

	import vyatta-resources-v1 {
		prefix resources;
	}

	import configd-v1 {
		prefix configd;
	}

	import vyatta-fw-types-v1 {
		prefix fw-types;
	}

	organization "AT&T Inc.";
	contact
		"AT&T
		 Postal: 208 S. Akard Street
		         Dallas, TX 75202, USA
		 Web: www.att.com";

	description
		"Copyright (c) 2019, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG submodule for Vyatta resource groups";

	revision 2015-12-09 {
		description "Moved protocol-group list out to separate " +
		        "submodule.";
	}
	revision 2015-11-25 {
		description "Initial revision " +
			"Relocate definitions from vyatta-resources-group-v1 " +
			"when refactoring to sub-modules.";
	}

	typedef group-address {
		type union {
			type types:ipv4-address {
				configd:help "IP address to match";
			}
			type types:ipv4-prefix {
				configd:help "IP subnet to match";
				configd:normalize "normalize ipv4-prefix";
			}
			type types:ipv6-address {
				configd:help "IPv6 address to match";
			}
			type types:ipv6-prefix {
				configd:help "IPv6 subnet to match";
				configd:normalize "normalize ipv6-prefix";
			}
		}
	}

	typedef group-port {
		type union {
			type fw-types:service-name;
			type types:port;
			type types:port-range;
		}
	}

	grouping group-icmp-numeric {
		list type {
			description "Choose a type (and optional code) by number";
			configd:help "Choose a type (and optional code) by number";
			key type-number;
			leaf type-number {
				type fw-types:icmp-type-number;
				description "ICMP type value";
				configd:help "ICMP type value";
			}
			list code {
				key code-number;
				leaf code-number {
					type fw-types:icmp-code-number;
				}
				description "ICMP code value";
				configd:help "ICMP code value";
			}
		}
	}

	augment /resources:resources {
		container group {
			configd:priority "300";
			description "Group of resources";
			configd:help "Group of resources";
			configd:validate "validate-resource-groups";
			configd:end "end-resource-groups";
			list icmp-group {
				description "Group of IPv4 ICMP";
				configd:help "Group of IPv4 ICMP";
				key "group-name";
				leaf group-name {
					type fw-types:group-name;
					description "Group of IPv4 ICMP";
					configd:help "Group of IPv4 ICMP";
				}
				leaf description {
					type string;
					description "IPv4 ICMP-group description";
					configd:help "IPv4 ICMP-group description";
				}
				leaf-list name {
					type fw-types:icmpv4-symbolic;
					description "Choose a type (and optional code) by name";
					configd:help "Choose a type (and optional code) by name";
				}
				uses group-icmp-numeric;
				must "count(name) + count(type/type-number) >= 1" {
					error-message "An 'icmp-group' must have at least one member";
				}
			}
			list icmpv6-group {
				description "Group of IPv6 ICMP";
				configd:help "Group of IPv6 ICMP";
				key "group-name";
				leaf group-name {
					type fw-types:group-name;
					description "Group of IPv6 ICMP";
					configd:help "Group of IPv6 ICMP";
				}
				leaf description {
					type string;
					description "IPv6 ICMP-group description";
					configd:help "IPv6 ICMP-group description";
				}
				leaf-list name {
					type fw-types:icmpv6-symbolic;
					description "Choose a type (and optional code) by name";
					configd:help "Choose a type (and optional code) by name";
				}
				uses group-icmp-numeric;
				must "count(name) + count(type/type-number) >= 1" {
					error-message "An 'icmpv6-group' must have at least one member";
				}
			}
			list port-group {
				description "Group of ports";
				configd:help "Group of ports";
				key "tagnode";
				leaf tagnode {
					description "Port-group name";
					type fw-types:group-name {
						configd:help "Port-group name";
						configd:syntax "syntax-check-port-group-name";
					}
					configd:help "Group of ports";
				}
				leaf description {
					type string;
					description "Port-group description";
					configd:help "Port-group description";
				}
				leaf-list port {
					type group-port;
					ordered-by "user";
					description "Port-group member";
					configd:help "Port-group member";
					max-elements 500;
				}
			}
			list address-group {
				description "Group of addresses and networks";
				configd:help "Group of addresses and networks";
				max-elements 1024;
				key "tagnode";
				leaf tagnode {
					description "Address-group name";
					type fw-types:group-name {
						configd:help "Address-group name";
					}
					configd:help "Group of addresses and networks";
				}
				leaf description {
					type string;
					description "Address-group description";
					configd:help "Address-group description";
				}
				leaf-list address {
					type group-address;
					ordered-by "user";
					description "Address-group member";
					configd:help "Address-group member";
				}
				list address-range {
					description "Address range";
					configd:help "Address range";
					key "start";
					leaf start {
						description "Start address";
						configd:help "Start address";
						type union {
							type types:ipv4-address {
								configd:help "IPv4 address";
							}
							type types:ipv6-address {
								configd:help "IPv6 address";
							}
						}
					}
					leaf to {
						description "End address";
						configd:help "End address";
						mandatory "true";
						must "(contains(current(), '.') and contains((../start), '.')) or (contains(current(), ':') and contains((../start), ':'))" {
							error-message "Cannot apply IPv4 and IPv6 addresses to a single range.  Use single address family per range";
						}
						type union {
							type types:ipv4-address {
								configd:help "IPv4 address";
							}
							type types:ipv6-address {
								configd:help "IPv6 address";
							}
						}
					}
				}
			}
		}
	}
}
