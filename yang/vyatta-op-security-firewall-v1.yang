module vyatta-op-security-firewall-v1 {
	namespace "urn:vyatta.com:mgmt:vyatta-op-security-firewall:1";
	prefix vyatta-op-security-firewall-v1;

	import vyatta-opd-extensions-v1 {
		prefix opd;
	}
	import vyatta-op-show-v1 {
		prefix show;
	}
	import vyatta-op-show-log-v1 {
		prefix show-log;
	}
	import vyatta-op-clear-v1 {
		prefix clear;
	}
	import vyatta-op-monitor-v1 {
		prefix monitor;
	}
	import vyatta-op-npf-types-v1 {
		prefix op-npf-types;
	}
	import vyatta-security-firewall-v1 {
		prefix fw;
	}

	organization "AT&T Inc.";
	contact
		"AT&T
		 Postal: 208 S. Akard Street
		         Dallas, TX 75202, USA
		 Web: www.att.com";

	description
		"Copyright (c) 2017-2021, AT&T Intellectual Property.
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for firewall-related operation mode commands.";

	revision 2020-02-08 {
		description "Escalate privilege of show/clear firewall";
	}

	revision 2019-11-14 {
		description "Correct spellings of 'specified'";
	}

	revision 2019-02-08 {
		description "Make 'show firewall' suggest 'lo' as interface.";
	}

	revision 2018-09-26 {
		description "For pattern-help use opd instead of configd.
			     Extend options for clearing statistics.
			     Require zone-based firewall feature.";
	}

	revision 2018-04-04 {
		description "Add local-zone option to zone-policy.";
	}

	revision 2018-01-24 {
		description "Update logging to get info from journalctl.";
	}

	revision 2017-09-14 {
		description "Conversion from node files.";
	}

	opd:augment /show:show {

		opd:command firewall {
			opd:help "Show dataplane firewall information";
			opd:on-enter "vyatta-dp-npf-show-rules all: fw-in fw-out local bridge zone";
			opd:inherit "" {
				opd:privileged true;
			}

			opd:command detail {
				opd:help "Show dataplane firewall detail information";
				opd:on-enter "vyatta-dp-npf-show-rules --detail all: fw-in fw-out local bridge zone";
			}

			opd:argument name {
				opd:help "Show dataplane firewall information";
				type op-npf-types:op-ifname;
				opd:allowed "vyatta-interfaces.pl --show all";
				opd:on-enter "vyatta-dp-npf-show-rules interface:$3 fw-in fw-out local bridge zone";
			}
		}

		opd:command zone-policy {
			if-feature fw:zone-based-firewall;
			opd:help "Show dataplane zone-policy information";
			opd:on-enter "vyatta-show-zone.pl";

			opd:option zone {
				opd:help "Show zone policy for a specific zone";
				type op-npf-types:op-zone-name;
				opd:allowed "allowed-nodes security zone-policy zone";
				opd:on-enter "vyatta-show-zone.pl --zone=$4";
			}

			opd:command local-zone {
				opd:help "Show zone policy for the local zone";
				opd:on-enter "vyatta-show-zone.pl --local-zone";
			}
		}
	}

	opd:augment /show:show/show-log:log {

		opd:command firewall {
			opd:help "Show log for firewall";

			opd:option name {
				opd:help "Show log for the specified firewall";
				type op-npf-types:op-ruleset-name;
				opd:allowed "allowed-nodes security firewall name";
				opd:on-enter 'npf-show-logs "(fw|bridge|local) rule $5:[0-9]+ "';

				opd:option rule {
					opd:help "Show log for a rule in the specified firewall";
					type op-npf-types:op-rule-number;
					opd:allowed "allowed-nodes security firewall name ${COMP_WORDS[4]} rule";
					opd:on-enter 'npf-show-logs "(fw|bridge|local) rule $5:$7 "';
				}
			}
		}
	}

	opd:augment /clear:clear {

		opd:command firewall {
			opd:help "Clear firewall statistics";
			opd:on-enter "vyatta-dp-npf-clear fw";
			opd:inherit "" {
				opd:privileged true;
			}

			opd:command bridge {
				opd:help "Clear bridge statistics";
				opd:on-enter "vyatta-dp-npf-clear bridge";
			}

			opd:option interface {
				opd:help "Clear statistics for the specified interface";
				type op-npf-types:op-ifname;
				opd:allowed "vyatta-interfaces.pl --show=all --includes=firewall";
				opd:on-enter 'vyatta-dp-npf-clear fw interface $4';

				opd:option dir {
					opd:help "Clear statistics for specified direction";
					type op-npf-types:op-direction;
					opd:allowed "allowed-nodes `vyatta-interfaces.pl --conf-line --dev=${COMP_WORDS[3]}` firewall";
					opd:on-enter 'vyatta-dp-npf-clear fw interface $4 dir $6';

					opd:option name {
						opd:help "Clear statistics for specified ruleset";
						type op-npf-types:op-ruleset-name;
						opd:allowed "allowed-nodes `vyatta-interfaces.pl --conf-line --dev=${COMP_WORDS[3]}` firewall ${COMP_WORDS[5]}";
						opd:on-enter 'vyatta-dp-npf-clear fw interface $4 dir $6 name $8';
						opd:option rule {
							opd:help "Clear statistics for specified rule";
							type op-npf-types:op-rule-number;
							opd:allowed "allowed-nodes security firewall name ${COMP_WORDS[7]} rule";
							opd:on-enter 'vyatta-dp-npf-clear fw interface $4 dir $6 name $8 rule ${10}';
						}
					}
				}

				opd:option name {
					opd:help "Clear statistics for specified ruleset";
					type op-npf-types:op-ruleset-name;
					opd:allowed "allowed-nodes security firewall name";
					opd:on-enter 'vyatta-dp-npf-clear fw interface $4 name $6';
					opd:option rule {
						opd:help "Clear statistics for specified rule";
						type op-npf-types:op-rule-number;
						opd:allowed "allowed-nodes security firewall name ${COMP_WORDS[5]} rule";
						opd:on-enter 'vyatta-dp-npf-clear fw interface $4 name $6 rule $8';
					}
				}
			}
		}

		opd:command zone-policy {
			if-feature fw:zone-based-firewall;
			opd:help "Clear zone statistics";
			opd:on-enter "vyatta-dp-npf-clear zone";
			opd:inherit "" {
				opd:privileged true;
			}

			opd:option from {
				opd:help "Clear statistics for the specified 'from' zone";
				type op-npf-types:op-zone-name;
				opd:allowed "allowed-nodes security zone-policy zone";
				opd:on-enter 'vyatta-dp-npf-clear zone from $4';

				opd:option to {
					opd:help "Clear statistics for specified 'to' zone";
					type op-npf-types:op-zone-name;
					opd:allowed "allowed-nodes security zone-policy zone ${COMP_WORDS[3]} to";
					opd:on-enter 'vyatta-dp-npf-clear zone from $4 to $6';

					opd:option name {
						opd:help "Clear statistics for specified ruleset";
						type op-npf-types:op-ruleset-name;
						opd:allowed "allowed-nodes security zone-policy zone ${COMP_WORDS[3]} to ${COMP_WORDS[5]} firewall";
						opd:on-enter 'vyatta-dp-npf-clear zone from $4 to $6 name $8';
						opd:option rule {
							opd:help "Clear statistics for specified rule";
							type op-npf-types:op-rule-number;
							opd:allowed "allowed-nodes security firewall name ${COMP_WORDS[7]} rule";
							opd:on-enter 'vyatta-dp-npf-clear zone from $4 to $6 name $8 rule ${10}';
						}
					}
				}
			}
		}
	}

	opd:augment /monitor:monitor {

		opd:command firewall {
			opd:help "Monitor firewall";

			opd:option name {
				opd:help "Monitor the specified firewall";
				type op-npf-types:op-ruleset-name;
				opd:allowed "allowed-nodes security firewall name";
				opd:on-enter 'vyatta-monitor FIREWALL "(fw|bridge|local) rule $4:[0-9]+ "';

				opd:option rule {
					opd:help "Monitor a rule in the specified firewall";
					type op-npf-types:op-rule-number;
					opd:allowed "allowed-nodes security firewall name ${COMP_WORDS[3]} rule";
					opd:on-enter 'vyatta-monitor FIREWALL "(fw|bridge|local) rule $4:$6 "';
				}
			}
		}
	}
}
